MakeAChoice DEFINITIONS IMPLICIT TAGS ::= BEGIN

IMPORTS BoolMod2 FROM OtherModule;

Collection ::= SEQUENCE {
     the-choice CHOICE {
         hello [0] OCTET STRING,
         goodbye [1] OCTET STRING,
         integer [2] INTEGER,
         boolean [3] BoolMod2,
         sequence [4] SEQUENCE { i INTEGER }
     }
}

END

OtherModule DEFINITIONS IMPLICIT TAGS ::= BEGIN

BoolMod2 ::= BOOLEAN

END

ExplicitChoice DEFINITIONS ::= BEGIN

MySequence ::= SEQUENCE {

}

MyChoice ::= CHOICE {
    hello [0] OCTET STRING,
    goodbye [1] OCTET STRING,
    integer [2] INTEGER,
    boolean [3] BOOLEAN,
    sequence [4] MySequence
}

END

SimpleChoice DEFINITIONS ::= BEGIN

Simple ::= CHOICE {
    a INTEGER,
    b OCTET STRING
}

END

Clashing DEFINITIONS ::= BEGIN

Clash ::= CHOICE {
    a [ 98] IMPLICIT INTEGER,
    b [ 99] IMPLICIT OCTET STRING,
    c [100] IMPLICIT OCTET STRING
}

END

ChoiceOfChoice DEFINITIONS ::= BEGIN

C ::= CHOICE {
    one CHOICE {
        a [1] IMPLICIT OCTET STRING,
        b [2] IMPLICIT OCTET STRING
    },
    two CHOICE {
        c [3] IMPLICIT OCTET STRING,
        d [4] IMPLICIT OCTET STRING
    }
}

END
