Circular DEFINITIONS IMPLICIT TAGS ::= BEGIN

CircularSequence1 ::= SEQUENCE {
    name OCTET STRING,
    cs2 CircularSequence2 OPTIONAL
}

CircularSequence2 ::= SEQUENCE {
    cs1 CircularSequence1
}

CircularSequenceOf1 ::= SEQUENCE {
    sequence CircularSequenceOf2
}

CircularSequenceOf2 ::= SEQUENCE OF CircularSequenceOf1

CircularChoice1 ::= CHOICE {
    int INTEGER,
    choice [1] EXPLICIT CircularChoice2,
    seq SEQUENCE { inner SEQUENCE { number MyInt } },
    enum ENUMERATED { one, two }
}

CircularChoice2 ::= SEQUENCE {
    str OCTET STRING,
    choice CircularChoice1
}

MyInt ::= INTEGER

SelfReference ::= CHOICE {
    str [0] OCTET STRING,
    self [1] SelfReference
}

END-- Comment at end
