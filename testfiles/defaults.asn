Defaults

DEFINITIONS EXPLICIT TAGS ::=

BEGIN

defined_int INTEGER           ::= -172803790

SequenceWithDefault ::= SEQUENCE
{
    integer INTEGER DEFAULT 88,
    flag    BOOLEAN DEFAULT FALSE,
    string  OCTET STRING DEFAULT "dog",
    defined INTEGER DEFAULT defined_int,
    colour  Colour DEFAULT blue,
    real    REAL   DEFAULT 5523432.12323,
    ...
}

Colour ::= ENUMERATED
{
    red,
    green,
    blue
}

END
