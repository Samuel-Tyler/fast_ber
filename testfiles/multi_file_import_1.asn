MultiModuleA DEFINITIONS IMPLICIT TAGS ::= BEGIN
IMPORTS
    StringInModuleB, string-value FROM MultiModuleB
    IntegerInModuleC, integer-value FROM MultiModuleC;

Collection ::= SEQUENCE {
    string StringInModuleB,
    integer IntegerInModuleC
}

END
