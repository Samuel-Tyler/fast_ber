MultiModuleB DEFINITIONS IMPLICIT TAGS ::= BEGIN
EXPORTS StringInModuleB;

StringInModuleB ::= OCTET STRING

string-value StringInModuleB ::= "pear"

END

MultiModuleC DEFINITIONS IMPLICIT TAGS ::= BEGIN
EXPORTS IntegerInModuleC;

IntegerInModuleC ::= INTEGER

integer-value IntegerInModuleC ::= 5

END
