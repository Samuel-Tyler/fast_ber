Parameterized DEFINITIONS EXPLICIT TAGS ::= BEGIN

T1 ::= OCTET STRING

T2{X} ::= SEQUENCE {
    a INTEGER,
    b X
}

T3 ::= T2{T1}

T4 ::= SEQUENCE {
    a T2{ INTEGER },
    b T2{ OCTET STRING }
}

END
