Sequence DEFINITIONS IMPLICIT TAGS ::= BEGIN

Empty ::= [10] SEQUENCE {
}

Collection ::= SEQUENCE {
    empty   [0] Empty,
    null    [1] NULL,
    integer [2] INTEGER,
    boolean [3] BOOLEAN,
    string  [4] UTF8String
}

Contents ::= SEQUENCE {
    seq   SEQUENCE {
        enu   ENUMERATED {
            value   (5)
        },
        integer INTEGER
    },
    cho   CHOICE {
        boolean BOOLEAN,
        string  UTF8String
    }
}

Components ::= SEQUENCE {
    COMPONENTS OF Contents
}

END
