Simple DEFINITIONS AUTOMATIC TAGS ::= BEGIN

Collection ::= SEQUENCE {
    hello OCTET STRING,
    goodbye -- inline comment test -- OCTET STRING,
    integer INTEGER,
    boolean BOOLEAN,
    ...
}

END
