Simple DEFINITIONS IMPLICIT TAGS ::= BEGIN

Greetings ::= SEQUENCE {
    hello [0] OCTET STRING,
    goodbye [1] OCTET STRING
}

Collection ::= SEQUENCE {
    COMPONENTS OF Greetings,
    integer [2] INTEGER,
    boolean [3] BOOLEAN,
    child [4] Child,
    optional-child [5] Child OPTIONAL,
    the-choice [6] CHOICE {
        hello [0] OCTET STRING,
        goodbye [1] OCTET STRING,
        integer [2] INTEGER,
        boolean [3] BOOLEAN,
        ...
    },
    ...
}

Child ::= SEQUENCE {
    meaning-of-life [0] INTEGER OPTIONAL,
    list [1] SEQUENCE OF OCTET STRING,
    ...
}

END-- Comment at end
