TopLevel DEFINITIONS AUTOMATIC TAGS ::= BEGIN

Collection ::= SEQUENCE {
    --my-choice MyChoice,
    my-int MyInt,
    my-string MyString
}

MyChoice ::= CHOICE {
    hello OCTET STRING,
    integer INTEGER
}

MyInt ::= INTEGER
MyString ::= OCTET STRING

END
